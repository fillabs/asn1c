-- OK: Everything is fine

-- Behavioral regression test for CVE-2025-32893.
--
-- SetA and SetB intentionally reuse the SAME &id (1) but bind it to
-- DIFFERENT types (IntPayload vs StrPayload). Message.second is
-- parameterized by SetB, so its open type at id 1 must decode as an
-- IA5String. Without comparing the VALUESET constraint during
-- parameterization, Message.second can silently reuse SetA's table instead.

-- iso.org.dod.internet.private.enterprise (1.3.6.1.4.1)
-- .spelio.software.asn1c.test (9363.1.5.1)
-- .212

ModuleIosValuesetBehavior
    { iso org(3) dod(6) internet (1) private(4) enterprise(1)
        spelio(9363) software(1) asn1c(5) test(1) 212 }
    DEFINITIONS AUTOMATIC TAGS ::=
BEGIN

    Id ::= INTEGER

    P ::= CLASS {
        &id     Id UNIQUE,
        &Type
    } WITH SYNTAX { TYPE &Type IDENTIFIED BY &id }

    IntPayload  ::= INTEGER
    BoolPayload ::= BOOLEAN
    StrPayload  ::= IA5String
    OctPayload  ::= OCTET STRING

    SetA P ::= {
        {TYPE IntPayload  IDENTIFIED BY 1} |
        {TYPE BoolPayload IDENTIFIED BY 2}
    }

    SetB P ::= {
        {TYPE OctPayload  IDENTIFIED BY 2} |
        {TYPE StrPayload  IDENTIFIED BY 1}
    }

    Message ::= SEQUENCE {
        first   SpecializedContent {{SetA}},
        second  SpecializedContent {{SetB}}
    }

    SpecializedContent {P : Set} ::= SEQUENCE {
        id      P.&id({Set}),
        value   P.&Type({Set}{@id})
    }

END
