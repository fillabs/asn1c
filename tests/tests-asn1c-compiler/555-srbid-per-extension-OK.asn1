-- OK: Everything is fine

-- iso.org.dod.internet.private.enterprise (1.3.6.1.4.1)
-- .spelio.software.asn1c.test (9363.1.5.1)
-- .555

-- Regression test for GitHub issue #555: F1AP SRBID encoding.
--
-- The SRBID type in 3GPP 38.473 v19.3.0 is INTEGER (0..3, ...)
-- (or INTEGER (0..3, ..., 4..255) in some versions).  The PER encoder
-- must preserve the extension bit and encode root-range values in 2 bits
-- (not fold the extension additions into the root range and emit 8 bits).
--
-- Without the CPR_ignore_extension_additions fix, INTEGER (0..3, ..., 4..255)
-- would generate range_bits=8 (root widened to 0..255) instead of range_bits=2
-- (root stays 0..3).  A value of 1 encoded in 8 bits as [ext=0][00000001]
-- would be misread by a spec-conformant decoder expecting [ext=0][01] (2 bits),
-- returning SRBID=0 instead of SRBID=1.

ModuleSRBID
    { iso org(3) dod(6) internet (1) private(4) enterprise(1)
        spelio(9363) software(1) asn1c(5) test(1) 555 }
    DEFINITIONS AUTOMATIC TAGS ::=
BEGIN

    -- Baseline: extension marker only, no named additions.
    -- Must generate: APC_CONSTRAINED | APC_EXTENSIBLE, range_bits=2, lb=0, ub=3
    SRBID ::= INTEGER (0..3, ...)

    -- With named extension additions: the 4..255 range must NOT widen the
    -- root to 0..255 (8 bits).  Root must stay 0..3 (2 bits).
    SRBID-ext ::= INTEGER (0..3, ..., 4..255)

END
