-- OK: Everything is fine

-- iso.org.dod.internet.private.enterprise (1.3.6.1.4.1)
-- .spelio.software.asn1c.test (9363.1.5.1)
-- .164

ModuleClassDefaultSyntax
	{ iso org(3) dod(6) internet (1) private(4) enterprise(1)
		spelio(9363) software(1) asn1c(5) test(1) 164 }
	DEFINITIONS AUTOMATIC TAGS ::=
BEGIN

DCLASS ::= CLASS {
&id INTEGER,
&Type
}

Ordered DCLASS ::= {
{&id 1, &Type UTF8String} |
{&id 2, &Type OCTET STRING}
}

Unordered DCLASS ::= {
{&Type UTF8String, &id 17} |
{&id 8, &Type OCTET STRING}
}

A ::= SEQUENCE
{
a-Ordered-id DCLASS.&id ({Ordered}),
a-Ordered-val DCLASS.&Type ({Ordered}{@a-Ordered-id})
}

B ::= SEQUENCE
{
b-Unordered-id DCLASS.&id ({Unordered}),
b-Unordered-val DCLASS.&Type ({Unordered}{@b-Unordered-id})
}

END
