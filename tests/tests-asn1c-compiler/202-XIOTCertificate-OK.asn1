XIOTCertificate DEFINITIONS EXPLICIT TAGS ::= BEGIN

Certificate ::= SEQUENCE {
  tbsCertificate      TBSCertificate,
  signatureAlgorithm  SignatureIdentifier,
  signature           BIT STRING
}

TBSCertificate ::=  SEQUENCE {
  version [0] INTEGER {v3(2)},
  serialNumber INTEGER (1..MAX),
  signature SignatureIdentifier,
  issuer Name,
  validity Validity,
  subject Name,
  subjectPublicKeyInfo SubjectPublicKeyInfo,
  extensions [3] Extensions OPTIONAL
}

SignatureIdentifier ::= SEQUENCE {
  algorithm OBJECT IDENTIFIER (ecdsa-with-SHA256)
}

Name ::= SEQUENCE SIZE (1) OF DistinguishedName

DistinguishedName ::= SET SIZE (1) OF CommonName

CommonName ::= SEQUENCE {
  type OBJECT IDENTIFIER (id-at-commonName),
  value UTF8String
  -- If CA, value is CA name, else EUI-64 in format
  -- "01-23-54-67-89-AB-CD-EF"
}

Validity ::= SEQUENCE {
  notBefore UTCTime,
  notAfter UTCTime
  -- In format "YYMMDDhhmmssZ"
}

SubjectPublicKeyInfo ::= SEQUENCE {
  algorithm AlgorithmIdentifier,
  subjectPublicKey BIT STRING
}

AlgorithmIdentifier ::= SEQUENCE {
  algorithm OBJECT IDENTIFIER (id-ecPublicKey),
  parameters OBJECT IDENTIFIER (prime256v1)
}

Extensions ::= SEQUENCE SIZE (1..MAX) OF Extension

Extension ::= SEQUENCE {
  extnId OBJECT IDENTIFIER,
  critical BOOLEAN DEFAULT FALSE,
  extnValue OCTET STRING
}

ansi-X9-62 OBJECT IDENTIFIER ::=
  { iso(1) member-body(2) us(840) 10045 }

id-ecPublicKey OBJECT IDENTIFIER ::=
  { ansi-X9-62 keyType(2) 1 }

prime256v1 OBJECT IDENTIFIER ::=
  { ansi-X9-62 curves(3) prime(1) 7 }

ecdsa-with-SHA256 OBJECT IDENTIFIER ::=
  { ansi-X9-62 signatures(4) ecdsa-with-SHA2(3) 2 }

id-at-commonName OBJECT IDENTIFIER ::=
  { joint-iso-itu-t(2) ds(5) attributeType(4) 3 }

END
