-- OK: Everything is fine

-- Regression for OPEN TYPE selection when an information object set row
-- omits the optional &Type field.

-- iso.org.dod.internet.private.enterprise (1.3.6.1.4.1)
-- .spelio.software.asn1c.test (9363.1.5.1)
-- .211

ModuleOpenTypeIOCRegression
	{ iso org(3) dod(6) internet(1) private(4) enterprise(1)
		spelio(9363) software(1) asn1c(5) test(1) 211 }
	DEFINITIONS AUTOMATIC TAGS ::=
BEGIN

	Id ::= INTEGER

	T ::= SEQUENCE {
		id     P.&id({Objs}),
		value  P.&Type({Objs}{@id})
	}

	P ::= CLASS {
		&id    Id UNIQUE,
		&Type  OPTIONAL
	} WITH SYNTAX { ID &id [TYPE &Type] }

	Objs P ::= {
		{ ID 0 } |
		{ ID 1 TYPE Payload }
	}

	Payload ::= BOOLEAN

	Message ::= SEQUENCE {
		procedureCode PROC.&procedureCode({PROC-SET}),
		msgValue PROC.&Value({PROC-SET}{@procedureCode})
	}

	PROC ::= CLASS {
		&procedureCode Id UNIQUE,
		&Value
	} WITH SYNTAX {
		[CODE &procedureCode]
		VALUE &Value
	}

	PROC-SET PROC ::= {
		{ VALUE PayloadSeq } |
		{ CODE 1 VALUE PayloadSeq }
	}

	PayloadSeq ::= SEQUENCE {
		n INTEGER (0..255)
	}

END
