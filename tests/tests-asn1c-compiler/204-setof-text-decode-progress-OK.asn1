-- OK: Everything is fine

-- Regression test: malformed XER/JER SET OF and SEQUENCE OF inputs must not
-- crash, read past the end of the input buffer, or spin on zero-consumption
-- successful element decodes.

-- iso.org.dod.internet.private.enterprise (1.3.6.1.4.1)
-- .spelio.software.asn1c.test (9363.1.5.1)
-- .204

ModuleSetOfTextDecodeProgress
    { iso org(3) dod(6) internet(1) private(4) enterprise(1)
        spelio(9363) software(1) asn1c(5) test(1) 204 }
    DEFINITIONS AUTOMATIC TAGS ::=
BEGIN

    SeqOfNull ::= SEQUENCE (SIZE(1)) OF NULL
    SeqOfString ::= SEQUENCE OF PrintableString (FROM("A".."Z"))
    SetOfString ::= SET OF PrintableString (FROM("A".."Z"))

END
