-- OK: Everything is fine

-- iso.org.dod.internet.private.enterprise (1.3.6.1.4.1)
-- .spelio.software.asn1c.test (9363.1.5.1)
-- .165

-- A parameterized type with a class-governed object set parameter
-- (X.683), as used by IEEE 1609.2 Extension {EXT-TYPE : ExtensionTypes}.
-- The code generator looks up the generic type without its parameters
-- to name the #include file. That lookup shall not report a FATAL
-- diagnostic (check-exit-status.sh).

ModuleClassGovernedObjectSetParameter
	{ iso org(3) dod(6) internet (1) private(4) enterprise(1)
		spelio(9363) software(1) asn1c(5) test(1) 165 }
	DEFINITIONS AUTOMATIC TAGS ::=
BEGIN

	EXT-TYPE ::= CLASS {
		&extId      INTEGER,
		&ExtContent
	} WITH SYNTAX {&ExtContent IDENTIFIED BY &extId}

	Extension {EXT-TYPE : ExtensionTypes} ::= SEQUENCE {
		id      EXT-TYPE.&extId({ExtensionTypes}),
		content EXT-TYPE.&ExtContent({ExtensionTypes}{@.id})
	}

	MyExtensions EXT-TYPE ::= { {BOOLEAN IDENTIFIED BY 1}, ... }

	MyExtension ::= Extension{{MyExtensions}}

END
